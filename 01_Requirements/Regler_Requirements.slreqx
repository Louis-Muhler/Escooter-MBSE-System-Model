# Regler_Requirements

## BAT_CTRL_1: Toleranz der Berechnung (Functional)
Das System muss den SOC (State of Charge) der Fahrzeugbatterie mit einer Toleranz von +- 5% berechnen

## BAT_CTRL_2: Ausfallsicherheit (Functional)
Das System muss bei Ausfall diesen selbstständig erkennen und an übergeordnete Systeme melden können.

## BAT_CTRL_3: Kalibrierungsmöglichkeit (Functional)
Das System muss durch geschultes Personal innerhalb von 10 Minuten kalibrierbar sein

## BAT_CTRL_4: Kalibrierungsgenauigkeit (Functional)
Das System muss seine Kalibrierungsgenauigkeit (Toleranz ±5%) für mindestens 24 Monate ohne Neukalibrierung beibehalten.

## BAT_CTRL_5: Reaktionszeit (Functional)
Das System muss nach Power-On innerhalb von 500ms Ausgabewerte senden.

## BAT_CTRL_6: Temperatur-Derating bei Übertemperatur (Functional)
Wenn die Zelltemperatur über 90 °C erreicht, muss der Nutzende innerhalb von maximal 1 Sekunde gewarnt werden.

## BAT_CTRL_7: Unterspannungsschutz (Functional)
Wenn die Spannung unter 30 Volt fällt, soll der Nutzende eine Fehlermeldung erhalten.

## BAT_CTRL_8: Batteriewarnung (Functional)
Wenn der SoC unter 20% fällt, soll der Nutzende über diesen Zustand informiert werden.

## BAT_CTRL_9: Fehlererkennung (Functional)
Wenn die Zelltemperatur 90 Grad oder höher ist, die Spannung unter 30 Volt fällt und/oder der SoC unter 20%, muss das System dies dem Nutzenden melden können.
