# EScooter_Requirements

## F1.1: Das System muss ohne Nutzereingabe still stehen (Functional)

## F1.2: Das System muss bei Nutzereingabe solange beschleunigen, bis [Event] (Functional)

### F1.2.1: Das System muss bei Nutzereingabe solange beschleunigen, bis die Höchstgeschwindigkeit [20km/h] aus eigener Leistung erreicht wird (Functional)

### F1.2.2: Das System muss bei Nutzereingabe solange beschleunigen, bis die Nutzereingabe stoppt (Functional)

### F1.2.3: Das System muss bei Nutzereingabe solange beschleunigen, bis Leistungsgrenze überschritten wird (Functional)

## F1.3: Das System muss kontinuierlich die Überschreitung der Höchstgeschwindigkeit [20km/h] und Leistungsgrenze prüfen und auf einen Maximalwert begrenzen (Functional)

## F1.4: Das System muss bei Betätigung der Bremse mit mindestens [3,5 m/s^2] verzögern (Functional)

## F1.5: Das System muss eine Steuerung der Fahrtrichtung bis [40°] ermöglichen (Functional)

## F2.1: Das System muss elektrische Energie in einer Form speichern können (Functional)

## F2.2: Das System muss über eine Schnittstelle für Haushaltssteckdosen mit Energie aufladbar sein (Functional)

## F2.3: Das System muss die Maximalleistung an den Ladezustand des Speichers anpassen (Functional)

## F2.4: Das System muss den Nutzer bei Überschreiten einer Schwelle im Ladezustand des Energiespeichern warnen (Functional)

## F3.1: Das System muss dem Nutzer während dem Betrieb visuell Informationen zur Verfügung stellen (Functional)

### F3.1.1: Aktuelle Geschwindigkeit (Functional)

### F3.1.2: Ladezustand Energiespeicher (Functional)

### F3.1.3: Aktuelle abgegebene Leistung (Functional)

## F3.2: Das System muss eine Möglichkeit haben, ein Warnsignal für andere Verkehrsteilnehmer abzugeben (Functional)

## F3.3: Das System muss eine Schnittstelle zu einer mobilen App bereitstellen. Übermittlung von [Daten] (Functional)

### F3.3.1: Übermittlung vom Standort des Systems (Functional)

### F3.3.1: Übermittlung Ladezustand Energiespeicher (Functional)

## F4.1: Das System muss über einen Mechanismus verfügen, der das Wegfahren versperrt (Functional)

## F4.2: Das System muss über einen Mechanismus verfügen, der das Wegfahren entsperrt (Functional)

## NF1.1: Das System muss bei einem vollgeladenen Energiespeicher eine Strecke von [20km] unter maximaler Traglast auf einer ebenen Strecke zurücklegen können. (Functional)

## NF1.2: Das System muss für eine maximale Traglast von [100kg] ausgelegt sein (Functional)

## NF1.3: Das System muss innerhalb von [30min] von [10%] Ladezustand bis [80%] Ladezustand aufgeladen werden können bei Raumtemperatur (20 °C) (Functional)

## NF1.4: Das System muss eine Leistung von maximal [1000W] kurzzeitig abgeben können ohne sich zu beschädigen (Functional)

## NF1.5: Das System muss dauerhaft eine Nenndauerleistung von maximal [500W] abgeben können (Functional)

## NF2.1: Das System muss ein Gesamtgewicht von weniger als [20kg] aufweisen (Functional)

## NF2.2: Das System muss über einen Mechanismus verfügen, der die physischen Dimensionen für die Lagerung reduziert. (Functional)

## NF2.3: Das System muss über einen Mechanismus verfügen, der einer einzelnen Person ermöglicht das System ergonomisch tragen zu können (Functional)

## NF3.1: Das System muss die Informationen (REQ F 3.1) bei verschiedenen Lichtverhältnissen deutlich lesbar präsentieren können (Functional)

## NF3.2: Das System muss sich während der Fahrt vollständig bedienen lassen ohne, dass der Nutzer die standardmäßigen Haltestellen loslassen muss (Functional)

## SAS1.1: Das System muss über eine Bremsmöglichkeit pro Rad verfügen (Functional)

## SAS1.2: Das System muss redundante Leuchtmittel beinhalten (Functional)

### SAS1.2.1: Frontleuchten für eine bessere Sicht bei Dunkelheit (Functional)

### SAS1.2.2: Rückleuchten für die bessere Sichtbarkeit (Functional)

## SAS1.3: Das System muss keine scharfen Kanten oder Grate aufweisen (Functional)

## SAS1.4: Das System muss die Batterietemperatur kontinuierlich überwachen und sicherstellen dass kritische Temperatur [90°] nicht überschritten werden (Functional)

### SAS1.4.1: Während der Fahrt (Functional)

### SAS1.4.2: Während des Ladens (Functional)

## SAS1.5: Das System muss einen sicheren Stand auf der Tragfläche ermöglichen (Functional)

### SAS1.5.1: Durch eine Tragfläche mit einer Größe von mindestens [500 x 250mm] (Functional)

### SAS1.5.2: Durch Tragfläche mit Reibungskoeffizient von mindestens [1,15] (Functional)

## SAS1.6: Das System muss einen sicheren Griff an den Griffen ermöglichen (Functional)

### SAS1.6.1: Durch ergonomisch geformte Griffe (Functional)

### SAS1.6.2: Durch Griffe mit Reibungskoeffizient von mindestens [1] (Functional)

## SAS1.7: Das System muss das Wegschleudern von Steinen auf andere Verkehrsteilnehmer verringern (Functional)

## SAS1.8: Das System muss bei Systemstart seine einzelne Komponenten auf Funktion prüfen (Functional)

## SAS1.9: Das System muss einen wirksamen Schutz gegen das direkte Berühren aller spannungsführenden Bauteile aufweisen (Functional)

## SAS2.1: Das System muss vor Benutzung eine Authentifizierung des Nutzers erfordern, erst dann wird (Functional)

### SAS2.1.1: Die Wegfahrsperre entsperrt (Functional)

### SAS2.1.2: Der Antrieb entsperrt (Functional)

## SAS2.2: Das System muss so gestaltet sein, dass keine digitalen Schnittstellen von außerhalb des Gehäuses zugänglich sind (Functional)

## SAS2.3: Das System muss so gestaltet sein, dass der Zugang zum inneren des Gehäuses nur mit Spezialwerkzeug zerstörungsfrei zu öffnen ist (Functional)

## SAS2.4: Das System muss bei Systemstart seine einzelne Komponenten auf Integrität prüfen (Functional)
